# NapknbookAppStakeholderNeeds

## #1: Control Day Breaker (Functional)

### #3: Change Temperature Setting (Functional)

### #4: Change Light Setting (Functional)

## #2: Visit Imaginary Empires (Functional)
